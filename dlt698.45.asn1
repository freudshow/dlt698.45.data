DLT69845 DEFINITIONS ::= BEGIN

-----------------------------basic data type---------------------------------------
	Array ::= SEQUENCE OF Data
	Structure ::= SEQUENCE OF Data
	Bool ::= BOOLEAN
	Bit-string ::= BIT STRING
    DoubleLong ::= INTEGER(-2147483648..2147483647)
    DoubleLongUnsigned ::= INTEGER(0..4294967295)
	Octet-string ::= OCTET STRING
    Visible-string ::= VisibleString
    UTF8-string ::= UTF8String
	Integer8s ::= INTEGER(-128..127)
	Long ::= INTEGER(-32768..32767)
    Unsigned ::= INTEGER(0..255)
    LongUnsigned ::= INTEGER(0..65535)
    Long64 ::= INTEGER(-9223372036854775808..9223372036854775807)
    --Long64Unsigned ::= INTEGER(0..18446744073709551615)
	Long64Unsigned ::= BIT STRING(SIZE(64))
	Enum ::= INTEGER(0..255)
	Float32 ::= OCTET STRING(SIZE(4))
	Float64 ::= OCTET STRING(SIZE(8))

    Date-Time ::= SEQUENCE {
		year LongUnsigned,
		month Unsigned,
		dayOfMonth Unsigned,
		dayOfWeek Unsigned,
		hour Unsigned,
		minute Unsigned,
		second Unsigned,
		milliseconds LongUnsigned
	}

	Date ::= SEQUENCE {
		year LongUnsigned,
		month Unsigned,
		dayOfMonth Unsigned,
		dayOfWeek Unsigned
	}

	Time ::= SEQUENCE {
		hour Unsigned,
		minute Unsigned,
		second Unsigned
	}

	Date-Time-S ::= SEQUENCE { --  date_time_s
		year LongUnsigned,
		month Unsigned,
		dayOfMonth Unsigned,
		dayOfWeek Unsigned,
		hour Unsigned,
		minute Unsigned,
		second Unsigned
	}

	OI ::= LongUnsigned                 --对象标识

	OAD ::= SEQUENCE {                  --Object Attribute Descriptor, 对象属性描述符
		objId OI,                       --对象标识
        attrIdChara Unsigned,           --属性标识及其特征,  其中:
                                        --1. bit0...bit4 编码表示对象属性编号, 取值 0...31, 其中 0 表
                                        --示整个对象属性, 即对象的所有属性, 见 8.2.1;
                                        --2. bit5...bit7 编码表示属性特征, 属性特征是对象同一个属性
                                        --在不同快照环境下取值模式, 取值 0...7, 特征含义在具体类
                                        --属性中描述.
        attrElemIdx INTEGER(1..255)     --属性内元素索引: 00H 表示整个属性全部内容.如果属性是结构
                                        --或数组, 01H 指向对象属性的第一个元素;如果属性是记录型的存
                                        --储区, 非 0 值 n 表示最近第 n 次的记录.
    }

    OadList ::= SEQUENCE OF OAD
	ROAD ::= SEQUENCE {
		objDescr OAD,
		ralateObjDescr OadList
	}

	OMD ::= SEQUENCE {
		objId OI,
		methodId INTEGER(1..255),
		actionMode INTEGER(0)
	}

	TI::=SEQUENCE {
		unit ENUMERATED {
			sec  (0),
			minute (1),
			hour (2),
			day  (3),
			month  (4),
			year  (5)
		},
		interval LongUnsigned
	}

	TSA ::= Octet-string(SIZE(2..17))
	MAC ::= Octet-string
	RN ::= Octet-string                              --ESAM 生成用于加密的信息串。

    Region ::= SEQUENCE {
		regionUnit ENUMERATED {
			closeOpen (0),
			openClose (1),
			closeClose (2),
			openOpen (3)
		},
		start Data,
		end Data
	}

	ScalerUnit ::= SEQUENCE {
		conversion Integer8s,	    --换算-倍数因子的指数,基数为 10；如数值不是数字的,则换算应被置 0。
		unit PhysicalUnit		--物理单位, 详见698.45<表B.1 物理单位的枚举定义>, 其符号待以后添加
	}

	RSD ::= CHOICE {
		notSel [0] NULL,
		sel1 [1] Selector1,
		sel2 [2] Selector2,
		sel3 [3] Selector3,
		sel4 [4] Selector4,
		sel5 [5] Selector5,
		sel6 [6] Selector6,
		sel7 [7] Selector7,
		sel8 [8] Selector8,
		sel9 [9] Selector9,
		sel10 [10] Selector10
	}

	Selector1 ::= SEQUENCE {
		objDescr OAD,
		value Data
	}

	Selector2 ::= SEQUENCE {
		objDescr OAD,		--对象描述符
		startValue Data,	--起始值
		endValue Data,		--结束值
		interv Data			--数据间隔
	}

	Selector3 ::= SEQUENCE OF Selector2

	Selector4 ::= SEQUENCE {
		acqStartTime Date-Time-S,	--采集启动时间
		meterSet	 MS	            --电能表集合
	}

	Selector5 ::= SEQUENCE {
		acqStoreTime Date-Time-S,
		meterSet MS
	}

	Selector6 ::= SEQUENCE {
		acqStartTimeStartValue Date-Time-S,	--采集启动时间起始值
		acqStartTimeEndValue Date-Time-S,   --采集启动时间结束值
		timeInterv TI,						--时间间隔
		meterSet MS							--电能表集合
	}

	Selector7 ::= SEQUENCE {
		acqStoreTimeStartValue Date-Time-S,	--采集存储时间起始值
		acqStoreTimeEndValue Date-Time-S,	--采集存储时间结束值
		timeInterv TI,						--时间间隔
		meterSet MS							--电能表集合
	}

	Selector8 ::= SEQUENCE {
		acqSucTimeStartValue Date-Time-S,	--采集成功时间起始值
		acqSucTimeEndValue Date-Time-S,	    --采集成功时间结束值
		timeInterv TI,	                    --时间间隔
		meterSet MS	                        --电能表集合
	}

	Selector9 ::= SEQUENCE {
		upNRec Unsigned	--上n次记录
	}

	Selector10 ::= SEQUENCE {
		upNRecord Unsigned,	--上 n 条记录
		meterSet MS			--电能表集合
	}

	RCSD ::= SEQUENCE OF CSD

	CSD ::= CHOICE {
		oad [0] OAD,
		road [1] ROAD
	}

	MS ::= CHOICE	{
		noMeter                 [0] NULL,
		allAddr                 [1] NULL,
		aGrpUserType            [2] SEQUENCE OF Unsigned,	    --一组用户类型
		aGrpUserAddr            [3] SEQUENCE OF TSA,	        --一组用户地址
		aGrpCfgSeq              [4] SEQUENCE OF LongUnsigned,	--一组配置序号
		aGrpUserTypeInterv      [5] SEQUENCE OF Region,	        --一组用户类型区间
		aGrpUserAddrInterv      [6] SEQUENCE OF Region,	        --一组用户地址区间
		aGrpUserCfgSeqInterv    [7] SEQUENCE OF Region		    --一组配置序号区间
	}

	DAR ::= ENUMERATED {
		suc								(0),	--	成功
		hardInvalid						(1),	--	硬件失效
		invalidForMoment				(2),	--	暂时失效
		refuseRdWr						(3),	--	拒绝读写
		objNotDef						(4),	--	对象未定义
		objInterNotMatch				(5),	--	对象接口类不符合
		objNotExist						(6),	--	对象不存在
		typeNotMatch					(7),	--	类型不匹配
		overflow						(8),	--	越界
		dataBlkDisable					(9),	--	数据块不可用
		subframeTransCancle				(10),	--	分帧传输已取消
		notInSubframeTransState			(11),	--	不处于分帧传输状态
		cancleBlkWR						(12),	--	块写取消
		blkWRNotExist					(13),	--	不存在块写状态
		blkSeqInvalid					(14),	--	数据块序号无效
		passwdWrongOrNotPermit			(15),	--	密码错/未授权
		cannotModifyBaudrate			(16),	--	通信速率不能更改
		overflowYearInterval			(17),	--	年时区数超
		overflowDayInterval				(18),	--	日时段数超
		overflowRateCnt					(19),	--	费率数超
		securityCertificateNotMatch		(20),	--	安全认证不匹配
		repeatRecharge					(21),	--	重复充值
		esamAuthenticationFailed		(22),	--	ESAM验证失败
		saftyAuthenticationFailed		(23),	--	安全认证失败
		customerIDNotMatch				(24),	--	客户编号不匹配
		rechargeCntErr					(25),	--	充值次数错误
		electricityPurchasingOverflow	(26),	--	购电超囤积
		addrException					(27),	--	地址异常
		symmetricDecryptionErr			(28),	--	对称解密错误
		asymmetricDecryptionErr			(29),	--	非对称解密错误
		signatureErr					(30),	--	签名错误
		meterSuspend					(31),	--	电能表挂起
		timeTagInvalid					(32),	--	时间标签无效
		other							(-255)	--	其它
	}

    PhysicalUnit ::= ENUMERATED {--NOT COMPLETE
        a   (1),
        mo  (2),
        wk  (3),
        d   (4),
        h   (5),
        min (6),
        s   (7),
        rad (8),
        tK   (9),
        currency    (10),
        m   (11),
        mPerSec (12),
        squareMeter  (13),
        sqMeter (14),
        sqMeterPerHour  (15)
    }

	SID ::= SEQUENCE {
		identity DoubleLongUnsigned,
		appendData Octet-string
	}

	SID-MAC ::= SEQUENCE {
		saftyId SID,
		dataMAC MAC
	}

	BaudRate ::= ENUMERATED {
		baud300bps      (0),
        baud600bps      (1),
        baud1200bps     (2),
		baud2400bps     (3),
        baud4800bps     (4),
        baud7200bps     (5),
		baud9600bps     (6),
        baud19200bps    (7),
        baud38400bps    (8),
		baud57600bps    (9),
        baud115200bps   (10),
        autoAjust       (255)
	}

	Parity ::= ENUMERATED {
		no(0), odd(1), even(2)
	}

	DataBits ::= ENUMERATED {
		databit5(5), databit6(6),
		databit7(7), databit8(8)
	}

	StopBits ::= ENUMERATED {
		stopbits1(1), stopbits2(2)
	}

	FlowCtl ::= ENUMERATED {
		no(0), hard(1), soft(2)
	}

	COMDCB ::= SEQUENCE {
		baudrate BaudRate,
		parity Parity,
		databits DataBits,
		stopbits StopBits,
		flowctl FlowCtl
	}

    PIID ::= Unsigned       --PIID 用于客户机 APDU(Client-APDU)的服务数据类型中,  其中:
                            --bit7(服务优先级) 
                            --0: 普通优先级,  1:高优先级, 在应答 APDU
                            --中, 其值与请求的 APDU 相同.
                            --bit6（保留).
                            --bit0..bit5（服务序号): 二进制编码表示 0..63,  在应答 APDU 中,
                            --其值与请求的 APDU 相同.

    PIID-ACD ::= Unsigned   --PIID-ACD 用于服务器 APDU(Server-APDU)的服务数据类型中, 其中:
                            --bit7(服务优先级): 见 PIID.
                            --bit6(请求访问 ACD): 0:不请求, 1:请求。
                            --bit0..bit5(服务序号): 见 PIID.

    ConnectMechanismInfo ::= CHOICE {
        publicConnection	[0]	NullSecurity,  	    --公共连接
        pwdSec	 	        [1]	PasswordSecurity,  	--一般密码
        symmSec	 	        [2]	SymmetrySecurity,  	--对称加密
        sigSec	 	        [3]	SignatureSecurity	--数字签名
    }

    NullSecurity ::= NULL
    PasswordSecurity ::= Visible-string
    
    SymmetrySecurity ::= SEQUENCE{
        cipherText1 Octet-string, --密文1
        clientSig1  Octet-string  --客户机签名1
    }
    
    SignatureSecurity ::= SEQUENCE{
        cipherText2 Octet-string, --密文2
        clientSig2  Octet-string  --客户机签名2
    }

    ConnectResult ::= ENUMERATED{
        allowEstablishAppLink	 	(0)	,   --允许建立应用连接
        pwdInvalid	 	            (1)	,   --密码错误
        symmDecodeErr	 	        (2)	,   --对称解密错误
        asymmDecodeErr	 	        (3)	,   --非对称解密错误
        sigInvalid	 	            (4)	,   --签名错误
        protocolVerNotMatch	 	    (5)	,   --协议版本不匹配
        otherErr	 	            (255)   --	其他错误
    }

    ConnectResponseInfo ::= SEQUENCE{
        authResult ConnectResult,                   --认证结果
        authAnnexationInfo SecurityData OPTIONAL    --认证附加信息
    }

    SecurityData ::= SEQUENCE{
        svrRN RN, --服务器随机数
        svrSigInfo Octet-string --服务器签名信息
    }

	Data ::= CHOICE {
		null				[0] NULL,
		array				[1] SEQUENCE OF Data,
		structure			[2] SEQUENCE OF Data,
		bool				[3] Bool,
		bitString			[4] Bit-string,
		doubleLong			[5] DoubleLong,
		doubleLongunsigned	[6] DoubleLongUnsigned,
		octetString			[9] Octet-string,
		visibleString		[10] VisibleString,
		utf8String			[12] UTF8String,
		integer				[15] Integer8s,
		long				[16] Long,
		unsigned			[17] Unsigned,
		longunsigned		[18] LongUnsigned,
		long64				[20] Long64,
		long64Unsigned		[21] Long64Unsigned,
		enum				[22] Enum,
		float32				[23] Float32,
		float64				[24] Float64,
		dateTime			[25] Date-Time,
		date				[26] Date,
		time				[27] Time,
		date-Time-s			[28] Date-Time-S,
		oi					[80] OI,
		oad					[81] OAD,
		road				[82] ROAD,
		omd					[83] OMD,
		ti					[84] TI,
		tsa					[85] TSA,
		mac					[86] MAC,
		rn			     	[87] RN,
		region				[88] Region,
		scalerUnit			[89] ScalerUnit,
		rsd					[90] RSD,
		csd					[91] CSD,
		ms					[92] MS,
		sid					[93] SID,
		sidMac 	        	[94] SID-MAC,
		comdcb            	[95] COMDCB,
		rcsd              	[96] RCSD
	}

-----------------------------basic data type end------------------------------------

END
